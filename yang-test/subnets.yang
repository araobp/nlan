module subnets {

  yang-version 1;
  namespace "urn:araobp:nlan:subnets";
  prefix "subnets";
  contact "https://github.com/araobp";

  description "NLAN subnets module";
  revision 2015-10-07;

  list subnets {
    key vid;
    leaf vid {
      type uint16;
    }
    leaf vni {
      type uint32;
      mandatory true;
    }
    list ip_dvr {
      key addr;
      leaf addr {
        type string;
      }
      leaf mode {
        type string;
        mandatory true;
      }
      leaf dhcp {
        type string;
        default "diabled";
      }
    }
    leaf-list ports {
      type string;
    }
    leaf-list peers {
      type string;
    }
  }
}
