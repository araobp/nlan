module vxlan {

  yang-version 1;
  namespace "urn:araobp:nlan:vxlan";
  prefix "vxlan";
  contact "https://github.com/arapbp";

  description "NLAN vxlan module";
  revision 2015-10-07;

  list vxlan {
    key local_ip;
    leaf local_ip {
      type string;
    }
    leaf-list remote_ips {
      type string;
    }
  }
}
